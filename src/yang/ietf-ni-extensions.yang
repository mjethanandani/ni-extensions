module ietf-ni-extensions {
  yang-version "1.1";
  namespace "urn:ietf:params:xml:ns:yang:ietf-ni-extensions";
  prefix "ni-ext";

  import ietf-routing-types {
    prefix rt-types;
    reference
      "RFC 8294: Common YANG Data Types for the Routing Area.";
  }

  import ietf-network-instance {
    prefix ni;
    reference
      "RFC 8529: YANG Data Model for Network Instances.";
  }

  organization
    "IETF NETMOD Working Group";

  contact
    "WG Web:   <https://datatracker.ietf.org/wg/netmod/about>
     WG List:  <netmod@ietf.org>

     Editor: Mahesh Jethanandani (mjethanandani at gmail dot com).";

  description
    "This module augments the Network Instance (NI) YANG model 
     to add support for configuration of a Route Distinguisher (RD).

     Copyright (c) 2023 IETF Trust and the persons identified as
     authors of the code.  All rights reserved.

     Redistribution and use in source and binary forms, with or
     without modification, is permitted pursuant to, and subject
     to the license terms contained in, the Revised BSD 
     License set forth in Section 4.c of the IETF Trust's Legal
     Provisions Relating to IETF Documents
     (https://trustee.ietf.org/license-info).

     This version of this YANG module is part of RFC XXXX
     (https://www.rfc-editor.org/info/rfcXXXX); see the RFC itself
     for full legal notices.

     The key words 'MUST', 'MUST NOT', 'REQUIRED', 'SHALL', 'SHALL
     NOT', 'SHOULD', 'SHOULD NOT', 'RECOMMENDED', 'NOT 
     RECOMMENDED', 'MAY', and 'OPTIONAL' in this document are to
     be interpreted as described in BCP 14 (RFC 2119) (RFC 8174)
     when, and only when, they appear in all capitals, as shown
     here.";

  revision "YYYY-MM-DD" {
    description
      "Initial Version.";
    reference
      "RFC XXXX, A YANG Model for Network Instance Extensions.";
  }

  grouping rd {
    description
      "Grouping for Route Distinguisher extension.";

    container rd {
      description
        "Route distinguisher parameters.";
          
      leaf rd {
        type union {
          type rt-types:route-distinguisher;
          type enumeration {
            enum auto {
              description
                "Route distinguisher is assigned automatically.";
            }
          }
        }
        description
          "Route distinguisher value.";
        reference
          "RFC 4364: BGP/MPLS IP Virtual Private Networks (VPNs).";
      }

      leaf auto-rd {
        type rt-types:route-distinguisher;
        config false;
        description
          "Automatically assigned RD value when rd is configured
           as 'auto'.";
      }
    }
  }

  /*
   * Network Instance configuration.
   */
  augment "/ni:network-instances/ni:network-instance" {
    description
      "Augment network instance for per VRF parameters";
    uses rd;
  }
}
